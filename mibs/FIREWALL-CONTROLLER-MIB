FIREWALL-CONTROLLER-MIB DEFINITIONS ::= BEGIN

IMPORTS
    unix
        FROM SMUX-MIB
    MODULE-IDENTITY, OBJECT-TYPE, Unsigned32,
    INTEGER, OCTET STRING, OBJECT IDENTIFIER,
    IpAddress
        FROM SNMPv2-SMI
    DisplayString, RowStatus, DateAndTime
        FROM SNMPv2-TC;

firewallController MODULE-IDENTITY
    LAST-UPDATED "202110240000Z"
    ORGANIZATION "AO Koncern Sozvezdie"
    CONTACT-INFO
            ""
    DESCRIPTION
            "The Firewall Controller MIB module."
    ::= { unix 199 }

firewallControllerTable OBJECT-TYPE
    SYNTAX     SEQUENCE OF firewallControllerEntry
    MAX-ACCESS not-accessible
    STATUS     current
    DESCRIPTION
            ""
    ::= { firewallController 1 }

firewallControllerEntry OBJECT-TYPE
    SYNTAX     firewallControllerEntry
    MAX-ACCESS not-accessible
    STATUS     current
    DESCRIPTION
            ""
    INDEX      { fcIndex }
    ::= { firewallControllerTable 1 }

firewallControllerEntry ::= SEQUENCE {
    fcIndex           Unsigned32,
    fcSrcAddr         IpAddress,
    fcSrcMask         IpAddress,
    fcDstAddr         IpAddress,
    fcDstMask         IpAddress,
    fcInIface         OCTET STRING,
    fcOutIface        OCTET STRING,
    fcProto           INTEGER,
    fcSrcPortMin      Unsigned32,
    fcSrcPortMax      Unsigned32,
    fcDstPortMin      Unsigned32,
    fcDstPortMax      Unsigned32,
    fcState           BIT STRING,
    fcAction          INTEGER,
    fcActionParams    OCTET STRING,
    fcInverseFlags    BIT STRING,
    fcCommand         INTEGER
}

fcIndex OBJECT-TYPE
    SYNTAX     Unsigned32
    MAX-ACCESS not-accessible
    STATUS     current
    DESCRIPTION
            "Entry index"
    ::= { firewallControllerEntry 1 }

fcSrcAddr OBJECT-TYPE
    SYNTAX     IpAddress
    MAX-ACCESS read-create
    STATUS     current
    DESCRIPTION
            "Source ip address"
    ::= { firewallControllerEntry 2 }

fcSrcMask OBJECT-TYPE
    SYNTAX     IpAddress
    MAX-ACCESS read-create
    STATUS     current
    DESCRIPTION
            "Source network mask"
    ::= { firewallControllerEntry 3 }

fcDstAddr OBJECT-TYPE
    SYNTAX     IpAddress
    MAX-ACCESS read-create
    STATUS     current
    DESCRIPTION
            "Destination ip address"
    ::= { firewallControllerEntry 4 }

fcDstMask OBJECT-TYPE
    SYNTAX     IpAddress
    MAX-ACCESS read-create
    STATUS     current
    DESCRIPTION
            "Destination network mask"
    ::= { firewallControllerEntry 5 }

fcInIface OBJECT-TYPE
    SYNTAX     OCTET STRING
    MAX-ACCESS read-create
    STATUS     current
    DESCRIPTION
            "Input interface"
    ::= { firewallControllerEntry 6 }

fcOutIface OBJECT-TYPE
    SYNTAX     OCTET STRING
    MAX-ACCESS read-create
    STATUS     current
    DESCRIPTION
            "Output interface"
    ::= { firewallControllerEntry 7 }

fcProto OBJECT-TYPE
    SYNTAX     INTEGER
                       {
                        none(0),
                        icmp(1),
                        tcp(6),
                        udp(17)
                       }
    MAX-ACCESS read-create
    STATUS     current
    DESCRIPTION
            "OSI-4 protocol"
    ::= { firewallControllerEntry 8 }

fcSrcPortMin OBJECT-TYPE
    SYNTAX     Unsigned32
    MAX-ACCESS read-create
    STATUS     current
    DESCRIPTION
            "Source port range left-value"
    ::= { firewallControllerEntry 9 }

fcSrcPortMax OBJECT-TYPE
    SYNTAX     Unsigned32
    MAX-ACCESS read-create
    STATUS     current
    DESCRIPTION
            "Source port range right-value"
    ::= { firewallControllerEntry 10 }

fcDstPortMin OBJECT-TYPE
    SYNTAX     Unsigned32
    MAX-ACCESS read-create
    STATUS     current
    DESCRIPTION
            "Destination port range left-value"
    ::= { firewallControllerEntry 11 }

fcDstPortMax OBJECT-TYPE
    SYNTAX     Unsigned32
    MAX-ACCESS read-create
    STATUS     current
    DESCRIPTION
            "Destination port range right-value"
    ::= { firewallControllerEntry 12 }

fcState OBJECT-TYPE
    SYNTAX     BIT STRING
                       {
                        none(0),
                        invalid(1),
                        established(2),
                        related(4),
                        new(8),
                       }
    MAX-ACCESS read-create
    STATUS     current
    DESCRIPTION
            "Connection state"
    ::= { firewallControllerEntry 13 }

fcAction OBJECT-TYPE
    SYNTAX     INTEGER
                       {
                        unknown(0),
                        accept(1),
                        drop(2),
                        reject(3),
                        snat(4),
                        dnat(5)
                       }
    MAX-ACCESS read-create
    STATUS     current
    DESCRIPTION
            "Netfilter action"
    ::= { firewallControllerEntry 14 }

fcActionParams OBJECT-TYPE
    SYNTAX     OCTET STRING
    MAX-ACCESS read-create
    STATUS     current
    DESCRIPTION
            "Action parameters"
    ::= { firewallControllerEntry 15 }

fcInverseFlags OBJECT-TYPE
    SYNTAX     BIT STRING
                        {
                         dport(0),
                         proto(1),
                         sport(2),
                         daddr(3),
                         saddr(4),
                         state(5),
                         outif(6),
                         inif(7)
                        }
    MAX-ACCESS read-create
    STATUS     current
    DESCRIPTION
            "Rule conditions inverse flags"
    ::= { firewallControllerEntry 16 }

fcCommand OBJECT-TYPE
    SYNTAX     INTEGER
                       {
                        add(0),
                        delete(1)
                       }
    MAX-ACCESS read-write
    STATUS     current
    DESCRIPTION
            "Table entry commands"
    ::= { firewallControllerEntry 17 }


fcPolicy OBJECT-TYPE
    SYNTAX     INTEGER
                       {
                        drop(0),
                        accept(1)
                       }
    MAX-ACCESS read-write
    STATUS     current
    DESCRIPTION
            "Default action"
    ::= { firewallController 2  }


auditEventsTable OBJECT-TYPE
    SYNTAX     SEQUENCE OF auditEventsEntry
    MAX-ACCESS not-accessible
    STATUS     current
    DESCRIPTION
            ""
    ::= { firewallController 3 }

auditEventsEntry OBJECT-TYPE
    SYNTAX     auditEventsEntry
    MAX-ACCESS not-accessible
    STATUS     current
    DESCRIPTION
            ""
    INDEX      { fcIndex }
    ::= { auditEventsTable 1 }

auditEventsEntry ::= SEQUENCE {
    fcAIndex           Unsigned32,
    fcALevel           INTEGER,
    fcAMessage         OCTET STRING,
    fcADate            DateAndTime
}

fcAIndex OBJECT-TYPE
    SYNTAX     Unsigned32
    MAX-ACCESS not-accessible
    STATUS     current
    DESCRIPTION
            "Entry index"
    ::= { auditEventsEntry 1 }

fcALevel OBJECT-TYPE
    SYNTAX     INTEGER
                       {
                        none(0),
                        easy(1),
                        medium(2),
                        hard(3)
                       }
    MAX-ACCESS read-only
    STATUS     current
    DESCRIPTION
            "Audit event level"
    ::= { auditEventsEntry 2 }

fcAMessage OBJECT-TYPE
    SYNTAX     OCTET STRING
    MAX-ACCESS read-only
    STATUS     current
    DESCRIPTION
            "Audit event message"
    ::= { auditEventsEntry 3 }

fcADate OBJECT-TYPE
    SYNTAX     DateAndTime
    MAX-ACCESS read-only
    STATUS     current
    DESCRIPTION
            "Audit event timestamp"
    ::= { auditEventsEntry 4 }


fcAControl OBJECT-TYPE
    SYNTAX     INTEGER
                       {
                        none(0),
                        easy(1),
                        medium(2),
                        hard(3)
                       }
    MAX-ACCESS read-write
    STATUS     current
    DESCRIPTION
            "Audit level controlling"
    ::= { firewallController 4  }


END
